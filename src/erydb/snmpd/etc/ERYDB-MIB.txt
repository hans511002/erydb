ERYDB-MIB DEFINITIONS ::= BEGIN
IMPORTS ucdExperimental, ucdavis FROM UCD-SNMP-MIB;
--IMPORTS ucdavis FROM UCD-SNMP-MIB;

-- v1 trap
demotraps OBJECT IDENTIFIER ::= { ucdExperimental 990 }

demo-trap TRAP-TYPE
	STATUS current
	ENTERPRISE demotraps
	VARIABLES { sysLocation }
	DESCRIPTION "This is just a demo"
	::= 17

-- v2 trap
erydb-trap OBJECT IDENTIFIER ::= { ucdavis 991 }

--alarm NOTIFICATION-TYPE
--	STATUS current
--	DESCRIPTION "erydb alarm notification"
--        ::= { demonotifs 17 }

-- alarmData contains alarm info of all the following
-- fields, which in the same format of agent trap alarm
-- data as: CALALARM-alarmID-comID-state-pname-pid-tid
-- this is to easy the trap handler processing
-- the individual fields are for the future snmp get/set to work

alarmData OBJECT-TYPE
	SYNTAX	DisplayString
    MAX-ACCESS	accessible-for-notify
	STATUS current
	DESCRIPTION "Fault component ID"
        ::= { erydb-trap 17 }

componentID OBJECT-TYPE
	SYNTAX	DisplayString
    MAX-ACCESS	accessible-for-notify
	STATUS current
	DESCRIPTION "Fault component ID"
        ::= { erydb-trap 18 }
        
alarmID NOTIFICATION-TYPE
	SYNTAX	Integer32
    MAX-ACCESS	accessible-for-notify
	STATUS current
	DESCRIPTION "alarm ID"
        ::= { erydb-trap 19 }        

state NOTIFICATION-TYPE
	SYNTAX	Integer32
    MAX-ACCESS	accessible-for-notify
	STATUS current
	DESCRIPTION "set or clear"
        ::= { erydb-trap 20 }   

sname NOTIFICATION-TYPE
	SYNTAX	DisplayString
    MAX-ACCESS	accessible-for-notify
	STATUS current
	DESCRIPTION "Reporting Server Name"
        ::= { erydb-trap 21 }
        
pname NOTIFICATION-TYPE
	SYNTAX	DisplayString
    MAX-ACCESS	accessible-for-notify
	STATUS current
	DESCRIPTION "Reporting Process Name"
        ::= { erydb-trap 22 }
        
pid NOTIFICATION-TYPE
	SYNTAX	Integer32
    MAX-ACCESS	accessible-for-notify
	STATUS current
	DESCRIPTION "Process ID"
        ::= { erydb-trap 23 }
        
tid NOTIFICATION-TYPE
	SYNTAX	Integer32
    MAX-ACCESS	accessible-for-notify
	STATUS current
	DESCRIPTION "Thread ID"
        ::= { erydb-trap 24 }
                   
END
